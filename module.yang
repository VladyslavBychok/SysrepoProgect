module Network {
	namespace "urn: Network";
	prefix mn;

	container commutator {

		container subscribers {

			list subscriber {
				key number;
				leaf number {
					type string;
				}

				leaf userName {
					type string;
					config false;
				}

				leaf incomingNumber {
					type string;
				}
		
				leaf state {
					type string;
				}	
		
			} 	
		
		}
	}
}
